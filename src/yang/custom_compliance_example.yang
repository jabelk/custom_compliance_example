module custom_compliance_example {

  namespace "http://example.com/custom_compliance_example";
  prefix custom_compliance_example;

  import ietf-inet-types {
    prefix inet;
  }
  import tailf-common {
    prefix tailf;
  }
  import tailf-ncs {
    prefix ncs;
  }

  description
    "Bla bla...";

  revision 2016-01-01 {
    description
      "Initial revision.";
  }

  container action {
    tailf:action double {
      tailf:actionpoint custom_compliance_example-action;
      input {
        leaf number {
          type string;
        }
      }
      output {
        leaf result {
          type string;
        }
      }
    }
  }
  list custom_compliance_example {
    description "This is an RFS skeleton service";

    key name;
    leaf name {
      tailf:info "Unique service id";
      tailf:cli-allow-range;
      type string;
    }

    uses ncs:service-data;
    ncs:servicepoint custom_compliance_example-servicepoint;

    // may replace this with other ways of refering to the devices.
    leaf-list device {
      type leafref {
        path "/ncs:devices/ncs:device/ncs:name";
      }
    }

        leaf-list report_categories {
          type enumeration {
            enum "wan";
            enum "banner";
            enum "snmp";
            enum "interfaces";
            enum "vty";
          }
    }



  //   // replace with your own stuff here
  //   leaf report_type {
  //     type inet:ipv4-address;
  //   }
  }
}
